Module-name-1 DEFINITIONS AUTOMATIC TAGS ::= 
BEGIN

Identifier ::= INTEGER (0..5)

Num ::= INTEGER (0..15)
Priority ::= ENUMERATED {high, low}

ASequence ::=
 SEQUENCE {
  priority Priority,
  scr Identifier,
  dst Identifier,
  num Num,
  length INTEGER (0..1024)
}

AChoice ::=
 CHOICE {
  identity Identifier,
  num Num
}

END


Module-name-2 DEFINITIONS AUTOMATIC TAGS ::= 
BEGIN

IMPORTS Identifier FROM Module-name-1;

Id ::= Identifier

SeqMod2 ::=
 SEQUENCE {
 isvalide BOOLEAN,
 name IA5String,
 identity Id
 }
 
END
